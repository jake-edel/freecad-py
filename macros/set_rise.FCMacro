from PySide import QtGui

userInput = QtGui.QInputDialog.getText(None, "Stair Run",  "Enter stair run in decimal feet ex. '3.5'")

if userInput[1]:
    stairRise = userInput[0]  + " ft"
    App.getDocument('rail_variable_angle').getObject('Sketch').setDatum(30,App.Units.Quantity(stairRise))
