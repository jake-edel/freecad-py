# -*- coding: utf-8 -*-

# Macro Begin: /home/jakob/Code/freecad/Macros/Make Visible.FCMacro +++++++++++++++++++++++++++++++++++++++++++++++++
import FreeCAD

Gui.getDocument("generated_rail_2").getObject("vert_post01").Visibility=True
Gui.getDocument("generated_rail_2").getObject("top_rail01").Visibility=True
Gui.getDocument("generated_rail_2").getObject("vert_post02").Visibility=True
Gui.activeDocument().activeView().viewIsometric()
Gui.SendMsgToActiveView("ViewSelection")
# Macro End: /home/jakob/Code/freecad/Macros/Make Visible.FCMacro +++++++++++++++++++++++++++++++++++++++++++++++++
